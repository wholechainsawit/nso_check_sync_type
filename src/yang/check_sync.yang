module check_sync {

  namespace "http://optimus.verizon.com/check-sync";
  prefix vz-check-sync;

  import ietf-inet-types {
    prefix inet;
  }
  import tailf-common {
    prefix tailf;
  }
  import tailf-ncs {
    prefix ncs;
  }

  augment "/ncs:services" {
    tailf:action get-services {
      tailf:actionpoint check-sync-get-services;
      output {
        list service {
          leaf path {
            type string;
          }
        }
      }
    }
  }
}
